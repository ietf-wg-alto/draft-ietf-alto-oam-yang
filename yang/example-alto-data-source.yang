module example-alto-data-source {
  yang-version 1.1;

  namespace "https://example.com/ns/example-alto-data-source";
  prefix ex-alto-ds;

  import ietf-alto {
    prefix alto;
    reference
      "RFC XXXX: YANG Data Models for the Application-Layer
                 Traffic Optimization (ALTO) Protocol";
  }

  import ietf-datastores {
    prefix ds;
    reference
      "RFC 8342: Network Management Datastore Architecture (NMDA)";
  }

  import ietf-yang-push {
    prefix yp;
    reference
      "RFC 8641: Subscription to YANG Notifications for Datastore
                 Updates";
  }

  import ietf-netconf-client {
    prefix ncc;
    reference
      "RFC HHHH: NETCONF Client and Server Models";
  }

  import ietf-restconf-client {
    prefix rcc;
    reference
      "RFC IIII: YANG Groupings for RESTCONF Clients and RESTCONF
                 Servers";
  }

  organization
    "Example, Inc.";

  contact
    "Example, Inc.
     Customer Service

     E-mail: alto-oam-yang@example.com";

  description
    "This module contains a collection of vendor-specific cases of
     data sources for ALTO.";

  revision 2026-02-04 {
    description
      "Version 1.0";
    reference
      "RFC XXXX: YANG Data Models for the Application-Layer
                 Traffic Optimization (ALTO) Protocol";
  }

  identity yang-datastore {
    base alto:source-type;
    description
      "Identity for data source of YANG-based datastore.";
  }

  identity protocol-type {
    description
      "Base identity for protocol type.";
  }

  identity netconf {
    base protocol-type;
    description
      "Identity for NETCONF protocol.";
  }

  identity restconf {
    base protocol-type;
    description
      "Identity for RESTCONF protocol.";
  }

  augment "/alto:alto/alto:alto-server/alto:data-source"
        + "/alto:source-params" {
    when 'derived-from-or-self(../alto:source-type,'
       + '"yang-datastore")';
    description
      "Example data source for local or remote YANG datastore.";
    container yang-datastore-source-params {
      description
        "YANG datastore specific configuration.";
      leaf datastore {
        type ds:datastore-ref;
        mandatory true;
        description
          "Reference of the datastore from which to get data.";
      }
      list target-paths {
        key name;
        description
          "XML Path Language (XPath) to subscribed YANG datastore
           node or subtree.";
        leaf name {
          type string;
          description
            "Name of the supported XPath or subtree filters.";
        }
        uses yp:selection-filter-types;
      }
      leaf protocol {
        type identityref {
          base protocol-type;
        }
        description
          "Indicates the protocol that is used to access the YANG
           datastore.";
      }
      container restconf {
        uses rcc:restconf-client-app-grouping {
          when 'derived-from-or-self(../protocol, "restconf")';
        }
        description
          "Parameters for the RESTCONF endpoint of the YANG
           datastore.";
      }
      container netconf {
        uses ncc:netconf-client-app-grouping {
          when 'derived-from-or-self(../protocol, "netconf")';
        }
        description
          "Parameters for the NETCONF endpoint of the YANG
           datastore.";
      }
    }
  }
}
